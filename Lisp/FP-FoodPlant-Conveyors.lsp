;;; FP-FoodPlant-Conveyors.lsp
;;; Sanitary / food-plant conveyor tool-palette library
;;; Units: inches. Insertion: infeed tail at 0,0  CL on Y=0  flow +X
;;; APPLOAD this file, then run FPSETUP and FPLIB

(vl-load-com)

(defun fp:layer (n col lt / )
  (if (not (tblsearch "LAYER" n))
    (entmake
      (list
        (cons 0 "LAYER")
        (cons 100 "AcDbSymbolTableRecord")
        (cons 100 "AcDbLayerTableRecord")
        (cons 2 n)
        (cons 70 0)
        (cons 62 col)
        (cons 6 (if lt lt "Continuous"))
      )
    )
  )
  (princ)
)

(defun c:FPSETUP ( / )
  (fp:layer "Q-CONV-BELT" 4 "Continuous")
  (fp:layer "Q-CONV-FRAM" 7 "Continuous")
  (fp:layer "Q-CONV-SUPP" 8 "Continuous")
  (fp:layer "Q-CONV-DRIV" 1 "Continuous")
  (fp:layer "Q-CONV-XFER" 6 "Continuous")
  (fp:layer "Q-CONV-SANI" 3 "HIDDEN")
  (fp:layer "Q-CONV-GUID" 2 "Continuous")
  (fp:layer "Q-CONV-CNTR" 2 "CENTER")
  (fp:layer "Q-CONV-FLOW" 1 "Continuous")
  (fp:layer "Q-CONV-ANNO" 7 "Continuous")
  (fp:layer "Q-CONV-HIDD" 8 "HIDDEN")
  (fp:layer "Q-CONV-CLR"  8 "PHANTOM")
  (fp:layer "Q-CONV-ZONE" 30 "Continuous")
  (fp:layer "Q-EQPM-INSP" 5 "Continuous")
  (if (not (tblsearch "STYLE" "FP-ANNO"))
    (command ".-style" "FP-ANNO" "romans.shx" "0.125" "1" "0" "N" "N" "N")
  )
  (princ "\nFPSETUP: food-plant conveyor layers and FP-ANNO style ready.")
  (princ)
)

(defun fp:line (p q lay)
  (entmakex
    (list (cons 0 "LINE") (cons 8 lay)
          (cons 10 p) (cons 11 q))
  )
)

(defun fp:circ (c r lay)
  (entmakex
    (list (cons 0 "CIRCLE") (cons 8 lay)
          (cons 10 c) (cons 40 r))
  )
)

(defun fp:txt (p h s lay)
  (entmakex
    (list (cons 0 "TEXT") (cons 8 lay) (cons 10 p)
          (cons 40 h) (cons 1 s) (cons 7 "FP-ANNO"))
  )
)

(defun fp:rect (p w h lay / x y)
  (setq x (car p) y (cadr p))
  (fp:line (list x y 0) (list (+ x w) y 0) lay)
  (fp:line (list (+ x w) y 0) (list (+ x w) (+ y h) 0) lay)
  (fp:line (list (+ x w) (+ y h) 0) (list x (+ y h) 0) lay)
  (fp:line (list x (+ y h) 0) (list x y 0) lay)
)

(defun fp:solid3 (a b c lay)
  (entmakex
    (list (cons 0 "SOLID") (cons 8 lay)
          (cons 10 a) (cons 11 b) (cons 12 c) (cons 13 c))
  )
)

(defun fp:att (p tag val h)
  (entmakex
    (list (cons 0 "ATTDEF") (cons 8 "Q-CONV-ANNO")
          (cons 10 p) (cons 40 h)
          (cons 1 val) (cons 2 tag) (cons 3 tag)
          (cons 70 0) (cons 7 "FP-ANNO"))
  )
)

(defun fp:draw-belt-pln (w l tob matl hyg drv / ow y0 x mid ss n)
  (c:FPSETUP)
  (setq ow (+ w 4.0)
        y0 (/ ow -2.0)
        mid (/ l 2.0))
  (fp:rect (list 0.0 y0 0.0) l ow "Q-CONV-FRAM")
  (fp:rect (list 0.0 (/ w -2.0) 0.0) l w "Q-CONV-BELT")
  (fp:line (list -6.0 0.0 0.0) (list (+ l 6.0) 0.0 0.0) "Q-CONV-CNTR")
  (fp:rect (list -1.0 (- y0 1.0) 0.0) (+ l 2.0) (+ ow 2.0) "Q-CONV-SANI")
  (fp:line (list 0.0 (- (/ w -2.0) 0.75) 0.0)
           (list l (- (/ w -2.0) 0.75) 0.0) "Q-CONV-GUID")
  (fp:line (list 0.0 (+ (/ w 2.0) 0.75) 0.0)
           (list l (+ (/ w 2.0) 0.75) 0.0) "Q-CONV-GUID")
  (fp:rect (list (- l 4.0) y0 0.0) 4.0 ow "Q-CONV-DRIV")
  (fp:solid3 (list l 0.0 0.0) (list (- l 6.0) 1.5 0.0) (list (- l 6.0) -1.5 0.0) "Q-CONV-FLOW")
  (fp:solid3 (list mid 0.0 0.0) (list (- mid 6.0) 1.5 0.0) (list (- mid 6.0) -1.5 0.0) "Q-CONV-FLOW")
  (fp:txt (list (- l 3.7) -1.1 0.0) 1.1 "DR" "Q-CONV-ANNO")
  (fp:txt (list 0.3 (- y0 2.2) 0.0) 1.0 "TU" "Q-CONV-ANNO")
  (setq x 12.0)
  (while (<= x (- l 12.0))
    (fp:rect (list (- x 1.0) (- y0 1.0) 0.0) 2.0 2.0 "Q-CONV-SUPP")
    (fp:rect (list (- x 1.0) (+ y0 ow -1.0) 0.0) 2.0 2.0 "Q-CONV-SUPP")
    (setq x (+ x 60.0))
  )
  (fp:txt (list (- mid 10.0) (+ (/ ow 2.0) 3.2) 0.0) 1.25
          (strcat (rtos w 2 0) " BELT x " (rtos l 2 0)) "Q-CONV-ANNO")
  (fp:att (list mid (+ (/ ow 2.0) 6.0) 0.0) "TAG" "CV-" 0.125)
  (fp:att (list mid (+ (/ ow 2.0) 7.5) 0.0) "WIDTH" (rtos w 2 0) 0.125)
  (fp:att (list mid (+ (/ ow 2.0) 9.0) 0.0) "LENGTH" (rtos l 2 0) 0.125)
  (fp:att (list mid (+ (/ ow 2.0) 10.5) 0.0) "TOB" (rtos tob 2 0) 0.125)
  (fp:att (list mid (+ (/ ow 2.0) 12.0) 0.0) "MATL" matl 0.125)
  (fp:att (list mid (+ (/ ow 2.0) 13.5) 0.0) "HYG" hyg 0.125)
  (fp:att (list mid (+ (/ ow 2.0) 15.0) 0.0) "BELT" "TPU" 0.125)
  (fp:att (list mid (+ (/ ow 2.0) 16.5) 0.0) "DRIVE" drv 0.125)
  (fp:att (list mid (+ (/ ow 2.0) 18.0) 0.0) "FLOW" "L-R" 0.125)
  (fp:att (list mid (+ (/ ow 2.0) 19.5) 0.0) "ZONE" "PROC" 0.125)
  (princ)
)

(defun fp:draw-belt-elv (w l tob / rail x)
  (c:FPSETUP)
  (setq rail 3.5)
  (fp:line (list 0.0 tob 0.0) (list l tob 0.0) "Q-CONV-BELT")
  (fp:rect (list 0.0 (- tob rail) 0.0) l rail "Q-CONV-FRAM")
  (fp:line (list 0.0 (- tob rail 5.0) 0.0) (list l (- tob rail 5.0) 0.0) "Q-CONV-HIDD")
  (fp:rect (list (- l 10.0) (- tob rail 8.0) 0.0) 10.0 8.0 "Q-CONV-DRIV")
  (fp:circ (list (- l 3.0) (- tob (/ rail 2.0)) 0.0) 2.5 "Q-CONV-DRIV")
  (fp:circ (list 3.0 (- tob (/ rail 2.0)) 0.0) 1.75 "Q-CONV-FRAM")
  (fp:rect (list -1.0 (- tob rail 12.0) 0.0) (+ l 2.0) 2.0 "Q-CONV-SANI")
  (setq x 12.0)
  (while (<= x (- l 12.0))
    (fp:line (list x 0.0 0.0) (list x (- tob rail) 0.0) "Q-CONV-SUPP")
    (fp:line (list (- x 6.0) 0.0 0.0) (list (+ x 6.0) 0.0 0.0) "Q-CONV-SUPP")
    (fp:circ (list x 0.0 0.0) 1.0 "Q-CONV-SUPP")
    (setq x (+ x 60.0))
  )
  (fp:line (list -6.0 0.0 0.0) (list (+ l 6.0) 0.0 0.0) "Q-CONV-ANNO")
  (fp:txt (list 2.0 (+ tob 1.6) 0.0) 1.25 (strcat "TOB " (rtos tob 2 0) "\"") "Q-CONV-ANNO")
  (fp:txt (list (- (/ l 2.0) 8.0) (+ tob 3.5) 0.0) 1.25
          (strcat (rtos w 2 0) " SANITARY BELT") "Q-CONV-ANNO")
  (princ)
)

(defun fp:draw-mod-pln (w l / )
  (fp:draw-belt-pln w l 36.0 "304" "L3" "END")
  (fp:txt (list 4.0 0.6 0.0) 0.9 "MODULAR" "Q-CONV-ANNO")
)

(defun fp:draw-roll-pln (w l / y0 x)
  (c:FPSETUP)
  (setq y0 (/ (+ w 4.0) -2.0))
  (fp:rect (list 0.0 y0 0.0) l (+ w 4.0) "Q-CONV-FRAM")
  (fp:line (list -6.0 0.0 0.0) (list (+ l 6.0) 0.0 0.0) "Q-CONV-CNTR")
  (setq x 3.0)
  (while (< x l)
    (fp:circ (list x 0.0 0.0) (/ w 2.0) "Q-CONV-BELT")
    (setq x (+ x 6.0))
  )
  (fp:txt (list 4.0 (+ (/ w 2.0) 3.0) 0.0) 1.1 "SS ROLLER" "Q-CONV-ANNO")
)

(defun fp:draw-scrw (dia l / r x pitch)
  (c:FPSETUP)
  (setq r (+ (/ dia 2.0) 0.5)
        pitch dia
        x 0.0)
  (fp:rect (list 0.0 (- r) 0.0) l (* 2.0 r) "Q-CONV-FRAM")
  (fp:line (list -4.0 0.0 0.0) (list (+ l 4.0) 0.0 0.0) "Q-CONV-CNTR")
  (while (< x l)
    (fp:line (list x (+ (- r) 0.2) 0.0)
             (list (min (+ x (/ pitch 2.0)) l) (- r 0.2) 0.0)
             "Q-CONV-BELT")
    (setq x (+ x (/ pitch 2.0)))
  )
  (fp:circ (list (+ l 3.0) 0.0 0.0) 4.0 "Q-CONV-DRIV")
  (fp:rect (list 8.0 4.0 0.0) 10.0 8.0 "Q-CONV-FRAM")
  (fp:txt (list 9.0 12.5 0.0) 1.0 "HOPPER" "Q-CONV-ANNO")
  (fp:txt (list 2.0 (- (+ r 3.0)) 0.0) 1.1
          (strcat "SCR " (rtos dia 2 0) "\" TUBULAR") "Q-CONV-ANNO")
)

(defun fp:draw-xfr (w / )
  (c:FPSETUP)
  (fp:circ (list 0.0 0.0 0.0) 0.5 "Q-CONV-XFER")
  (fp:rect (list -4.0 (- (/ w -2.0) 2.0) 0.0) 6.0 (+ w 4.0) "Q-CONV-FRAM")
  (fp:txt (list -3.0 (+ (/ w 2.0) 3.5) 0.0) 1.1
          (strcat "NOSE BAR " (rtos w 2 0) "\"") "Q-CONV-ANNO")
)

(defun fp:draw-std (h / )
  (c:FPSETUP)
  (fp:line (list -8.0 0.0 0.0) (list 8.0 0.0 0.0) "Q-CONV-SUPP")
  (fp:circ (list -6.0 0.0 0.0) 1.0 "Q-CONV-SUPP")
  (fp:circ (list 6.0 0.0 0.0) 1.0 "Q-CONV-SUPP")
  (fp:line (list -6.0 0.0 0.0) (list -6.0 4.0 0.0) "Q-CONV-SUPP")
  (fp:line (list 6.0 0.0 0.0) (list 6.0 4.0 0.0) "Q-CONV-SUPP")
  (fp:line (list -6.0 4.0 0.0) (list 6.0 4.0 0.0) "Q-CONV-SUPP")
  (fp:line (list 0.0 4.0 0.0) (list 0.0 h 0.0) "Q-CONV-SUPP")
  (fp:line (list -10.0 h 0.0) (list 10.0 h 0.0) "Q-CONV-FRAM")
  (fp:txt (list -8.0 (+ h 1.5) 0.0) 1.2 (strcat "H-STAND TOB " (rtos h 2 0) "\"") "Q-CONV-ANNO")
)

(defun fp:draw-dpan (w l / ow)
  (c:FPSETUP)
  (setq ow (+ w 6.0))
  (fp:rect (list 0.0 (/ ow -2.0) 0.0) l ow "Q-CONV-SANI")
  (fp:circ (list (/ l 2.0) (/ ow -2.0) 0.0) 0.75 "Q-CONV-SANI")
  (fp:txt (list 2.0 (+ (/ ow 2.0) 1.5) 0.0) 1.1 "DRIP PAN" "Q-CONV-ANNO")
)

(defun fp:draw-md (w / )
  (c:FPSETUP)
  (fp:rect (list 0.0 (- (/ w -2.0) 6.0) 0.0) 30.0 (+ w 12.0) "Q-EQPM-INSP")
  (fp:rect (list 4.0 (- (/ w -2.0) 2.0) 0.0) 22.0 (+ w 4.0) "Q-EQPM-INSP")
  (fp:line (list -6.0 0.0 0.0) (list 36.0 0.0 0.0) "Q-CONV-CNTR")
  (fp:rect (list 32.0 -8.0 0.0) 10.0 16.0 "Q-CONV-XFER")
  (fp:txt (list 5.0 (+ (/ w 2.0) 8.0) 0.0) 1.3
          (strcat "METAL DETECTOR " (rtos w 2 0) "\"") "Q-CONV-ANNO")
  (fp:txt (list 33.0 9.0 0.0) 1.0 "REJECT" "Q-CONV-ANNO")
)

(defun fp:draw-flow ( / )
  (c:FPSETUP)
  (fp:line (list 0.0 0.0 0.0) (list 18.0 0.0 0.0) "Q-CONV-FLOW")
  (fp:solid3 (list 18.0 0.0 0.0) (list 12.0 2.5 0.0) (list 12.0 -2.5 0.0) "Q-CONV-FLOW")
  (fp:txt (list 3.0 3.5 0.0) 1.2 "PRODUCT FLOW" "Q-CONV-ANNO")
)

(defun fp:get-w (def / v)
  (initget 6)
  (setq v (getreal (strcat "\nBelt / unit width inches <" (rtos def 2 0) ">: ")))
  (if v v def)
)

(defun fp:get-l (def / v)
  (initget 6)
  (setq v (getreal (strcat "\nLength inches <" (rtos def 2 0) ">: ")))
  (if v v def)
)

(defun c:FPBELT ( / w l tob matl hyg drv p)
  (setq w (fp:get-w 24.0)
        l (fp:get-l 96.0)
        tob 36.0
        matl "304"
        hyg "L3"
        drv "END")
  (initget 6)
  (setq p (getreal "\nTop of belt inches <36>: "))
  (if p (setq tob p))
  (setq matl (getstring T "\nMaterial 304/316 <304>: "))
  (if (= matl "") (setq matl "304"))
  (setq hyg (getstring T "\nHygiene L1-L5 <L3>: "))
  (if (= hyg "") (setq hyg "L3"))
  (setq drv (getstring T "\nDrive END/CTR/DRM <END>: "))
  (if (= drv "") (setq drv "END"))
  (fp:draw-belt-pln w l tob matl hyg drv)
  (princ "\nSanitary belt plan drawn. Use FPLIB to capture as a block.")
  (princ)
)

(defun c:FPBELTE ( / w l tob p)
  (setq w (fp:get-w 24.0) l (fp:get-l 96.0) tob 36.0)
  (initget 6)
  (setq p (getreal "\nTop of belt inches <36>: "))
  (if p (setq tob p))
  (fp:draw-belt-elv w l tob)
  (princ)
)

(defun c:FPMOD ( / w l)
  (setq w (fp:get-w 24.0) l (fp:get-l 96.0))
  (fp:draw-mod-pln w l)
  (princ)
)

(defun c:FPROLL ( / w l)
  (setq w (fp:get-w 24.0) l (fp:get-l 96.0))
  (fp:draw-roll-pln w l)
  (princ)
)

(defun c:FPSCRW ( / d l)
  (setq d (fp:get-w 6.0) l (fp:get-l 96.0))
  (fp:draw-scrw d l)
  (princ)
)

(defun c:FPXFR ( / w)
  (setq w (fp:get-w 24.0))
  (fp:draw-xfr w)
  (princ)
)

(defun c:FPSTD ( / h p)
  (setq h 36.0)
  (initget 6)
  (setq p (getreal "\nStand / TOB height inches <36>: "))
  (if p (setq h p))
  (fp:draw-std h)
  (princ)
)

(defun c:FPDPAN ( / w l)
  (setq w (fp:get-w 24.0) l (fp:get-l 96.0))
  (fp:draw-dpan w l)
  (princ)
)

(defun c:FPMD ( / w)
  (setq w (fp:get-w 18.0))
  (fp:draw-md w)
  (princ)
)

(defun c:FPFLOW ()
  (fp:draw-flow)
  (princ)
)

(defun fp:mkblk (name drawfn / ss)
  (if (tblsearch "BLOCK" name)
    (command ".-purge" "B" name "N")
  )
  (setq ss (ssget "_X"))
  (if ss
    (command ".erase" ss "")
  )
  (drawfn)
  (setq ss (ssget "_X"))
  (if ss
    (progn
      (command ".-block" name "0,0" ss "")
      (command ".-insert" name "0,0" "1" "1" "0")
    )
  )
)

(defun c:FPLIB ( / widths w name)
  (c:FPSETUP)
  (setq widths '(6.0 8.0 12.0 18.0 24.0 36.0 48.0))
  (foreach w widths
    (fp:mkblk
      (strcat "FP-CONV-BELT-PLN-" (if (< w 10.0) "0" "") (rtos w 2 0))
      (function (lambda () (fp:draw-belt-pln w 96.0 36.0 "304" "L3" "END")))
    )
    (fp:mkblk
      (strcat "FP-CONV-BELT-ELV-" (if (< w 10.0) "0" "") (rtos w 2 0))
      (function (lambda () (fp:draw-belt-elv w 96.0 36.0)))
    )
    (fp:mkblk
      (strcat "FP-CONV-MOD-PLN-" (if (< w 10.0) "0" "") (rtos w 2 0))
      (function (lambda () (fp:draw-mod-pln w 96.0)))
    )
  )
  (foreach w '(4.0 6.0 9.0 12.0 16.0)
    (fp:mkblk
      (strcat "FP-CONV-SCRW-PLN-" (if (< w 10.0) "0" "") (rtos w 2 0))
      (function (lambda () (fp:draw-scrw w 96.0)))
    )
  )
  (foreach w '(22.0 30.0 36.0 42.0 48.0)
    (fp:mkblk
      (strcat "FP-CONV-STD-H-" (rtos w 2 0))
      (function (lambda () (fp:draw-std w)))
    )
  )
  (fp:mkblk "FP-CONV-XFR-NOSE-24" (function (lambda () (fp:draw-xfr 24.0))))
  (fp:mkblk "FP-CONV-QC-MD-18" (function (lambda () (fp:draw-md 18.0))))
  (fp:mkblk "FP-CONV-ANNO-FLOW" (function (lambda () (fp:draw-flow))))
  (fp:mkblk "FP-CONV-PAN-DRP-24" (function (lambda () (fp:draw-dpan 24.0 96.0))))
  (princ "\nFPLIB complete. SAVEAS Blocks/FP-CONV-LIBRARY.dwg then ADCENTER > Create Tool Palette.")
  (princ)
)

(princ "\nFood Plant Conveyor palette LISP loaded. Commands: FPSETUP FPBELT FPBELTE FPMOD FPROLL FPSCRW FPXFR FPSTD FPDPAN FPMD FPFLOW FPLIB")
(princ)
